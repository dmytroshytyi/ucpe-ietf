module ietf-ucpe-ni-properties {
	yang-version 1.1;
	namespace "urn:ietf:params:xml:ns:yang:ietf-ucpe-ni-properties";
	prefix ietf-ucpe-ni;
	import ieee-dot1Q-types{
		prefix d1q;
		reference
			"Prefix dot1Q-types. Institute of Electrical and Electronics Engineers";
	}
	import ietf-logical-network-element {
		prefix lne;
		reference
			"RFC 8530: YANG Model for Logical Network Elements";
	}
	import ietf-network{
		prefix nw;
		reference
			"RFC 8345: YANG Data Model for Network Topologies";
	}
	import ietf-network-instance{
		prefix ni;
		reference
			"RFC 8529: YANG Data Model for Network Instances";
	}

	organization
		"SFR";
	contact
		"Dmytro Shytyi
		EMail:ietf.dmytro@shytyi.net";
	description
		"This is a YANG data model that extends Network Instance properties.

		Copyright (c) 2019 IETF Trust and the persons identified as
		authors of the code.  All rights reserved.

	Redistribution and use in source and binary forms, with or
	without modification, is permitted pursuant to, and subject to
	the license terms contained in, the Simplified BSD License set
	forth in Section 4.c of the IETF Trust's Legal Provisions
	Relating to IETF Documents
	(https://trustee.ietf.org/license-info).

	This version of this YANG module is part of RFC XXXX
	(https://www.rfc-editor.org/info/rfcXXXX); see the RFC itself
	for full legal notices.";

	revision 2019-11-27 {
		description
			"Added VLANs";
		reference
			"draft-shytyi-opsawg-vysm-07";
	}
	revision 2019-11-21 {
		description
			"Augmentation of RFC 8530";
		reference
			"draft-shytyi-opsawg-vysm-07";
	}
	revision 2019-10-28 {
		description
			"Yang model with vPorts assigned to the interfaces";
		reference
			"draft-shytyi-opsawg-vysm-05";
	}
	revision 2019-10-19 {
		description
			"Yang model was cleaned. Interfaces added";
		reference
			"draft-shytyi-opsawg-vysm-04";
	}
	revision 2019-09-16 {
		description
			"Added 0day config for VNFs.
			/bin/bash: :wq: command not found
			to the received comments.";
		reference
			"draft-shytyi-opsawg-vysm-00";
	}
	revision 2018-01-07 {
		description
			"Initial revision.";
		reference
			"draft-shytyi-netmod-vysm-01";
	}
	identity ni-area {
		description
			"Base identity for Network Interface (NI) - area";
	}
	identity lan {
		base ni-area;
		description
			"Identity for NI - area";
	}
	identity wan {
		base ni-area;
		description
			"Identity for NI - area";
	}
	identity wan2 {
		base ni-area;
		description
			"Identity for NI - area";
	}
	identity internal {
		base ni-area;
		description
			"Identity for NI - area. All uCPE NIs except LAN/WAN/WAN2";
	}
	augment "/ni:network-instances/ni:network-instance/"+ 
		"ni:root-type/ni:vsi-root" {
		container network-instance-properties {
			list sf-connection-points {
				key "sf-connection-point-id";
				leaf sf-connection-point-id {
					type string;
					description
						"Name of the connector";
				}
				container dot1q-vlan{
					leaf access-tag{
						type d1q:vid-range;
						description 
							"Acccess tag";
					}
//					leaf trunk-allowed-vlans{
//						type d1q:vid-range;
//					}	
					leaf-list trunk-allowed-vlans{
						type uint16{
							range "0..4095";
						}
					}
					leaf port-mode{
						type enumeration{
							enum trunk;
							enum access; 
						}
					}
					description
						"Dot1q encapsulation parameters";
				}
				description
					"Connection points of logical-network-element";
			}
			leaf ni-area {
				type identityref{
					base ni-area;
				}
				description
					"Area where ports of lne are attached";
			}
			description
				"Set of Virtual Network Function connectors";
			leaf supporting-node {
				type leafref{
					path "/nw:networks/nw:network/nw:node/nw:node-id";
				} 
				description
					"The reference to a physical node which hosts the logical element";
			}
		}
		description
			"Properties of network instance";
	}
}
