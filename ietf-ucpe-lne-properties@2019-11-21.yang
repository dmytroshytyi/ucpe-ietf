// File              : ietf-ucpe-lne-properties@2019-11-21.yang
// Author            : Dmytro Shytyi
// Site              : https://dmytro.shytyi.net
// Date              : 22.06.2020
// Last Modified Date: 22.06.2020
// Last Modified By  : Dmytro Shytyi
module ietf-ucpe-lne-properties {
	yang-version 1.1;
	namespace "urn:ietf:params:xml:ns:yang:ietf-ucpe-lne-properties";
	prefix ietf-ucpe;

	import ietf-logical-network-element {
		prefix lne;
		reference
			"RFC 8530: YANG Model for Logical Network Elements";
	}
	import ietf-network {
		prefix nw;
		reference
			"RFC 8345: YANG Data Model for Network Topologies";
	}

	include etsi-nfv-common-deviation;
	include etsi-nfv-vnf-deviation;

	organization
		"SFR";
	contact
		"Dmytro Shytyi
		EMail:ietf.dmytro@shytyi.net";
	description
		"This is a YANG module that extends the Logical Network Element
		properties.

	Copyright (c) 2019 IETF Trust and the persons identified as
	authors of the code.  All rights reserved.

	Redistribution and use in source and binary forms, with or
	without modification, is permitted pursuant to, and subject to
	the license terms contained in, the Simplified BSD License set
	forth in Section 4.c of the IETF Trust's Legal Provisions
	Relating to IETF Documents
	(https://trustee.ietf.org/license-info).

	This version of this YANG module is part of RFC XXXX
	(https://www.rfc-editor.org/info/rfcXXXX); see the RFC itself
	for full legal notices.";

	revision 2019-11-21 {
		description
			"Augmentation of RFC 8530";
		reference
			"draft-shytyi-opsawg-vysm-07";
	}
	revision 2019-10-28 {
		description
			"Yang model with vPorts assigned to the interfaces";
		reference
			"draft-shytyi-opsawg-vysm-05";
	}
	revision 2019-10-19 {
		description
			"Yang model was cleaned. Interfaces added";
		reference
			"draft-shytyi-opsawg-vysm-04";
	}
	revision 2019-09-16 {
		description
			"Added 0day config for VNFs.
		Yang model modified according
		to the received comments.";
		reference
			"draft-shytyi-opsawg-vysm-00";
	}
	revision 2018-01-07 {
		description
			"Initial revision.";
		reference
			"draft-shytyi-netmod-vysm-01";
	}
	augment "/lne:logical-network-elements/lne:logical-network-element" {
		container logical-network-element-properties {
			must "./supporting-node"{
				description "supporting-node is mandatory";
			}
			
			leaf vnfd {
				type leafref{
					path "/nfv/vnfd/id";
				}
			}	
			leaf supporting-node {
				type leafref{
					path "/nw:networks/nw:network/nw:node/nw:node-id";
				} 
				description
					"The reference to a physical node which hosts the logical element";
			}
			container simplified-lne-props{
				list sf-connection-points {
					key "sf-connection-point-id";
					leaf sf-connection-point-id {
						type string;
						description
							"Name of the connector";
					}
					description
						"Connection points of logical-network-element";
				}
				description
					"Set of Virtual Network Function connectors";
				leaf ram {
					type uint64;
					description
						"Size of RAM to allocate for
					the Guest OS";
					}
				leaf cpu {
					type uint64;
					description
						"Number of vCPUs to
					allocate for the sf";
					}
				list storages {
					key "id";
					leaf id {
						type string;
						description
							"Number of
						vDisk attached to the sf";
						}
					leaf location {
						type string;
						description
							"External location where
						the image (ex.qcow2) is saved.";
						}
					description
						"Virtual storge/vDisk
						attached to the Virtual Machine";
						}
			}
			container day0-config {
					leaf location {
					type string;
					description
						"0day configuration location";
				}
				leaf day0-var-path {
					type string;
					description
						"path of the file
						that contains the 0day variables";
				}
				list variable {
					key "name";
					leaf name {
						type string;
						description
							"variable name";
					}
					leaf value {
						type string;
						description
							"variable value";
					}
					description
						"list of variables";
				}
				description
					"0day configuration:init config";
			}
		}
		description
			"Properties of logic-network-element";
	}
        container nfv {
          list vnfd {
            key "id";

            description
              "A VNF Descriptor (VNFD) is a deployment template which
               describes a VNF in terms of deployment and operational
               behaviour requirements. It also contains connectivity,
               interface and virtualised resource requirements";
            reference
              "GS NFV-IFA011: Section 7.1.2, VNFD information element";

            uses vnfd;
          }
        }


}
